module frr-zebra-srv6 {
  yang-version 1.1;
  namespace "http://frrouting.org/yang/zebra-srv6";
  prefix frr-zebra-srv6;

  import ietf-inet-types {
    prefix inet;
  }
  
  import frr-zebra-sr {
    prefix a1;
  }

  import frr-srv6 {
    prefix frr-srv6;
  }

  organization
    "FRRouting";
  contact
    "FRR Users List:       <mailto:frog@lists.frrouting.org>
     FRR Development List: <mailto:dev@lists.frrouting.org>";
  description
    "This module defines zebra SRv6 settings
     This module refers Cisco-IOS-XR751-segment-routing-srv6-cfg

     Copyright 2021 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2021-12-21 {
    description
      "Initial revision";
  }

  augment "/a1:sr" {
    description
      "This augment extends the configuration data of
       'frr-zebra-sr'";

    container srv6 {
      description
        "Segment Routing with IPv6 dataplane";

      container locators {
        description
          "Configure SRv6 locators parameters";

        container locators {
          description
            "Configure SRv6 table of locators";
          
          list locator {
            key "name";
            description
              "Configure a SRv6 locator";

            container prefix {
              description
                "Specify locator prefix value";

              leaf prefix {
                type inet:ip-prefix;
                description
                  "IPv6 Prefix";
              }
            }
            /* End of container prefix */
            
            leaf name {
              type frr-srv6:srv6-locator-name;
              description
                "Locator name";
            }

            leaf status-up {
              type boolean;
              description
                "FRR Original: SRv6 locator used flag";
            }

            leaf block-bits-length {
              type uint8;
            }

            leaf node-bits-length {
              type uint8;
            }

            leaf function-bits-length {
              type uint8;
            }

            leaf argument-bits-length {
              type uint8;
            }
            
          }
          /* End of list locator */

        }
        /* End of container locators */

      }
      /* End of container locators */

    }
    /* End of container srv6 */

  }
  /* End of augment zebra */

}
